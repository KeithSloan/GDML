import time
import FreeCAD

def setNoExportProperty(obj):
    if not hasattr(obj, 'exportFlag'):
        obj.addProperty("App::PropertyBool", 'exportFlag', 'GDML', 'Export Flag')
        obj.exportFlag = False


def isrtObject(parent, obj):
    #print(f'Parent {parent}')
    if parent is None:
         new = doc.copyObject(obj)
    else:
         #print(f'Add object to {parent.Name}')
         new =  parent.addObject(doc.copyObject(obj))[0]
    return new
    

def getParent(obj):
       if hasattr(obj, 'InList'):
           for i, o in enumerate(obj.InList):
               if o.TypeId == 'App::Part':
                   return obj.InList[i]
       return None

def setCopyNumber(obj, cnCount):
    obj.addProperty("App::PropertyInteger", "CopyNumber","GDML").CopyNumber = cnCount
    return cnCount + 1

def setVolRef(obj, ref):
    obj.addProperty("App::PropertyString", "VolRef","GDML").VolRef = ref
    

def copyArrayObj(parent, Obj):
    new = None
    ignore = ['App::Origin', 'App::Line', 'App::Plane']
    print(f'Process Copy Obj : {Obj.Name}')
    if Obj.TypeId in ignore:
       return
    if hasattr(Obj,'ArrayType'):
        print(f'Is an Array : {Obj.Name}') 
        print(f'Process Array Base {baseObj.Base.Name} Placement {placement}')
        copyArrayObj(parent, Obj.Base)
    elif Obj.TypeId == 'App::Part' :
        parent = parent.newObject('App::Part', Obj.Name)
        parent.Placement = Obj.Placement
        # parent.Label = Obj.Name
    if hasattr(Obj, 'OutList'):
        if len(Obj.OutList) > 0:
            print(f'Part outList len {len(Obj.OutList)}')
            for obj in Obj.OutList:
                 print(obj.Name)
                 print(obj.TypeId)                           
                 copyArrayObj(parent, obj)
        else:
            print(f'Copy Object {Obj.Name}')
            parent = isrtObject(parent, Obj)
    else:
        print(f'Copy Object {Obj.Name}')
        parent = isrtObject(parent, Obj)
    #if Obj.Name[:6] == 'Origin' :
    #    new.Visibility = False 
    return parent

def printOutList(obj):
    print(f'Outlist {obj.Name}')
    for o in obj.OutList:
        print(o.Name)


def removeArray(array):
    ignore = ['App::Origin', 'App::Line', 'App::Plane']
    if hasattr(array, 'OutList'):
       for obj in array.OutList:
           # print(obj.Name)
           removeArray(obj)
    if array.TypeId not in ignore :
        print(f'Remove {array.Name}')
        FreeCAD.ActiveDocument.removeObject(array.Name)

def processArray(parent, arrayObj, cnCount):
    print(f'process Array {arrayObj.Name}')
    arrayVol = parent.newObject('App::Part', arrayObj.Name)
    # arrayVol.Label = arrayObj.Name
    newArrayObj = copyArrayObj(arrayVol, arrayObj.Base)
    # copyObj  May include Arrays that need expanding
    print(f'Now process {arrayVol.Name} : newArrayObj {newArrayObj.Name} : len {len(arrayObj.PlacementList)}')
    for p in arrayObj.PlacementList:
        cnCount = processObj(arrayVol, newArrayObj, cnCount, arrayObj.Placement*p)
    removeArray(arrayObj)
    

def processObj(parentVol, Obj, cnCount, placement):
    print(f'process Obj Parent{parentVol} {Obj.Name} Placement {placement}')
    
    new = parentVol.newObject('App::Link', 'Link_'+Obj.Name)
    # new.Label = 'Link_' + Obj.Name
    new.LinkedObject = Obj
    new.LinkPlacement = placement
    new.addProperty("App::PropertyString", "VolRef","GDML").VolRef = Obj.Name
    cnCount = setCopyNumber(new, cnCount)
    return cnCount


def processBaseObj(arrayFlag, parent, baseObj, cnCount, placement, placementList):
       # No longer used ?
       print(f'Process Base Obj : {baseObj.Name}')
       # Is this part of an Array expand for each item in placementList
       if arrayFlag == True:
           print(f'Len Placement List : {len(placementList)}')
           for p in placementList:
                  new, cnCount = processBaseObj(False, parent, baseObj, cnCount, placement*p, None)
       else:     
           # Is Base an  Array  
            if hasattr(baseObj,'ArrayType'):
                print(f'Is an Array : {baseObj.Name}') 
                print(f'Process Array Base {baseObj.Base.Name} Placement {placement}')
                new,  cnCount = processBaseObj(True, parent, baseObj.Base, cnCount, placement, baseObj.PlacementList)
            # is it a Part/Vol
            elif baseObj.TypeId == 'App::Part' :
                  print(f'process Part : {baseObj.Name}')
                  new = parent.newObject('App::Link', baseObj.Name)
                  new.LinkedObject = baseObj
                  new.LinkPlacement = placement
                  cnCount = setCopyNumber(new, cnCount)
                  # treat as a link so no need to process OutList other than embedded Array
                  if hasattr(baseObj, 'OutList'):
                     print(f'Part outllst len {len(baseObj.OutList)}')
                     for obj in baseObj.OutList:
                           print(obj.Name)
                           print(obj.TypeId)
                           # if obj.TypeId != 'App::Origin' and obj.TypeId !='App::FeaturePython':
                           if hasattr(obj, 'arrayFlag'):
                              if obj.arrayFlag == True:
                                  processBaseObj(False, newParent, obj, obj.Placement, None)
                           # else:
                           #    isrtObject(newParent, obj)
            # Is it a FeaturePython.
            elif baseObj.TypeId == 'Part::FeaturePython' :
                 print(f'Copy {baseObj.Name} Placement : {placement} Base Placement {baseObj.Placement}')
                 new = parent.newObject('App::Link', baseObj.Name)
                 new.LinkedObject = baseObj
                 cnCount = setCopyNumber(new, cnCount)
                 # new = isrtObject(parent, baseObj)                     
                 #new.Placement = baseObj.Placement*placement
                 #new.Placement = baseObj.Placement*placement
                 new.LinkPlacement = placement
                 new.Visibility = True
       if baseObj.TypeId  == 'App::FeaturePython':
             new = isrtObject(parent, baseObj)
       return new, cnCount 
  
def processSelected(array):
    # Array seems to have TypeId of Part::FeaturePython - test for ArrayType
    if not hasattr(array,'ArrayType'):
        print('Selection is Not an Array')
        return
    print(array.Base.Name)
    print(array.Base.InList)
    parent = getParent(array.Base)
    processArray(parent, array,1)
    # processBaseObj(True, parent, array.Base, 1, array.Placement, array.PlacementList)
    # setNoExportProperty(array)
    # array.Visibility = False

doc = App.ActiveDocument
sel = Gui.Selection.getSelection()
if len(sel) > 0:
    array = sel[0]
    start = time.time()
    processSelected(array)
    end = time.time()
    print(f'Duration : {end-start}')
    doc.recompute()
